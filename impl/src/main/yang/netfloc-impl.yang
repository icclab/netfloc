module netfloc-impl {
    yang-version 1;
    namespace "urn:opendaylight:params:xml:ns:yang:netfloc:impl";
    prefix "netfloc-impl";

    import config { prefix config; revision-date 2013-04-05; }
    import opendaylight-md-sal-binding { prefix md-sal-binding; revision-date 2013-10-28;}

    description
        "Service definition for netfloc project";

    revision "2014-12-10" {
        description
            "Initial revision";
    }

    identity netfloc {
        base config:module-type;
        config:java-name-prefix Netfloc;
    }

    augment "/config:modules/config:module/config:configuration" {
        case netfloc {
            when "/config:modules/config:module/config:type = 'netfloc'";
            container broker {
                uses config:service-ref {
                    refine type {
                        mandatory true;
                        config:required-identity md-sal-binding:binding-broker-osgi-registry;
                    }
                }
            }
        }
    }
}
